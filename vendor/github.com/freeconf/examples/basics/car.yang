/* 
  Interface definition for your service in YANG format described in IETF RFC 7950. 

  Here we define the management for our car application
 */
module car {
    prefix "car";
    namespace "freeconf.org/examples/basics/car";
    description "Vehicle of sorts";
    revision 0000-00-00;

    /*
      YANG has syntax for typical data structues
        container - struct
        leaf - primative field (string, int, ...)
        list - set of structs with or without an index key
    */
    container engine {
        container specs {
            leaf horsepower {
                type int32;
            }
        }
    }

    /* "uses X" is a way to reference definitions defined in a "grouping X". You'll
      see we have a "uses car" another place in this yang file */
    uses car;

    /* set of definitions for a car that can used anywhere "uses car" is found */
    grouping car {

        list tire {
            description "rubber circular part that makes contact with road";

            /* */
            key "pos";

            leaf pos {
                type int32;
            }
            leaf size {
                type string;
                default 15;
            }
            leaf worn {
                config false;
                type boolean;
            }
            leaf wear {
                config false;
                type decimal64;
            }
            leaf flat {
                config false;
                type boolean;
            }
        }

        /* config false means this is unsettable, which effecitvely makes is a metric */
        leaf miles {
            type int64;
            config false;
        }

        leaf running {
            type boolean;            
            config false;
        }  

        leaf lastRotation {
            type int64;
            config false;
        } 

        leaf speed {
            description "number of millisecs it takes to travel one mile";
            type int32;
            default 1000;
            units ms; // helpful for documentation but nothing progamatically is done with this units
        }
    }

    /* Events */

    notification update {
        description "important state information about your car";
        uses car;
    }

    /* Functions */

    rpc rotateTires {
        description "rotate tires for optimal wear";
    }

    rpc replaceTires {
        description "replace all tires";
    }

}
